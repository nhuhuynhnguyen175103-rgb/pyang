module l {tôi
  namespace urn:l;
  prefix l;thông

  revi

  list a {
    key id;
    max-elements unbounded;
    leaf id { type uint32; }
  }
  list b {
    key id;
    max-elements unbounded;
    leaf id { type uint32; }
  }
  list c {
    key id;
    max-elements 5;
    leaf id { type uint32; }
  }
  list d {
    key id;
    max-elements 5;
    leaf id { type uint32; }
  }
  list e {
    key id;
    leaf id { type uint32; }
  }
  list f {
    key id;
    max-elements unbounded;
    leaf id { type uint32; }
  }
}
